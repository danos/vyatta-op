module vyatta-op-traceroute-routing-instance-v1 {
	namespace "urn:vyatta.com:mgmt:vyatta-op-traceroute-routing-instance:1";
	prefix vyatta-op-traceroute-routing-instance-v1;

	import vyatta-opd-extensions-v1 {
		prefix opd;
	}
	import vyatta-routing-v1 {
		prefix routing;
	}
	import vyatta-op-traceroute-v1 {
		prefix traceroute;
	}

	organization "AT&T Inc.";
	contact
		"AT&T
		 Postal: 208 S. Akard Street
		 Dallas, TX 75202
		 Web: www.att.com";

	description
		"Copyright (c) 2019, AT&T Intellectual Property.
		 All rights reserved.

		 Redistribution and use in source and binary forms, with or without
		 modification, are permitted provided that the following conditions
		 are met:

		 1. Redistributions of source code must retain the above copyright
		    notice, this list of conditions and the following disclaimer.
		 2. Redistributions in binary form must reproduce the above
		    copyright notice, this list of conditions and the following
		    disclaimer in the documentation and/or other materials provided
		    with the distribution.
		 3. Neither the name of the copyright holder nor the names of its
		    contributors may be used to endorse or promote products derived
		    from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

		 Defines the 'traceroute' operational CLI for routing instance";

	revision 2019-03-13 {
		description "Initial version";
	}

	grouping option-routing-instance {
		opd:option routing-instance {
			opd:help "Track network path to <hostname|address> in routing-instance";
			opd:allowed "allowed-nodes routing routing-instance";
			type routing:routing-instance-name;
		}
	}

	opd:augment /traceroute:traceroute/traceroute:host {
		uses option-routing-instance;
	}

	opd:augment /traceroute:traceroute/traceroute:ipv4/traceroute:host {
		uses option-routing-instance;
	}

	opd:augment /traceroute:traceroute/traceroute:ipv6/traceroute:host {
		uses option-routing-instance;
	}
}
