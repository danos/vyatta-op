module vyatta-op-show-ip-ipv6-route-forward-v1 {
    namespace "urn:vyatta.com:mgmt:vyatta-op-show-ip-ipv6-route-forward:1";
    prefix vyatta-op-show-ip-ipv6-route-forward-v1;

    import vyatta-opd-extensions-v1 {
        prefix opd;
    }
    import vyatta-op-show-v1 {
        prefix op-show;
    }
    import vyatta-op-show-ip-ipv6-v1 {
        prefix op-show-ip-ipv6;
    }
    import vyatta-op-show-ip-ipv6-route-v1 {
        prefix op-show-ip-ipv6-route;
    }
    import vyatta-types-v1 {
		prefix types;
	}

    organization "AT&T Inc.";
    contact
        "AT&T
         Postal: 208 S. Akard Street
                 Dallas, TX 75202
         Web: www.att.com";

    description
        "Copyright (c) 2018-2019, AT&T Intellectual Property.
         All rights reserved.

         Redistribution and use in source and binary forms, with or without
         modification, are permitted provided that the following conditions
         are met:

         1. Redistributions of source code must retain the above copyright
            notice, this list of conditions and the following disclaimer.
         2. Redistributions in binary form must reproduce the above
            copyright notice, this list of conditions and the following
            disclaimer in the documentation and/or other materials provided
            with the distribution.
         3. Neither the name of the copyright holder nor the names of its
            contributors may be used to endorse or promote products derived
            from this software without specific prior written permission.

         THIS SOFTWARE IS PROVIDED BY THE COPYRIGHT HOLDERS AND CONTRIBUTORS
         'AS IS' AND ANY EXPRESS OR IMPLIED WARRANTIES, INCLUDING, BUT NOT
         LIMITED TO, THE IMPLIED WARRANTIES OF MERCHANTABILITY AND FITNESS
         FOR A PARTICULAR PURPOSE ARE DISCLAIMED. IN NO EVENT SHALL THE
         COPYRIGHT HOLDER OR CONTRIBUTORS BE LIABLE FOR ANY DIRECT, INDIRECT,
         INCIDENTAL, SPECIAL, EXEMPLARY, OR CONSEQUENTIAL DAMAGES (INCLUDING,
         BUT NOT LIMITED TO, PROCUREMENT OF SUBSTITUTE GOODS OR SERVICES;
         LOSS OF USE, DATA, OR PROFITS; OR BUSINESS INTERRUPTION) HOWEVER
         CAUSED AND ON ANY THEORY OF LIABILITY, WHETHER IN CONTRACT, STRICT
         LIABILITY, OR TORT (INCLUDING NEGLIGENCE OR OTHERWISE) ARISING IN
         ANY WAY OUT OF THE USE OF THIS SOFTWARE, EVEN IF ADVISED OF THE
         POSSIBILITY OF SUCH DAMAGE.

         SPDX-License-Identifier: BSD-3-Clause

         This module implements the IP(v6) kernel routes show CLI";

    revision 2019-05-07 {
        description "Allow IP address argument without prefix length";
    }
    revision 2018-11-02 {
        description "Initial revision";
    }

    opd:augment /op-show:show/op-show-ip-ipv6:ip/op-show-ip-ipv6-route:route {
        opd:command forward {
            opd:help "Show kernel route table";
            opd:on-enter "ip route list";
            opd:argument prefix {
                type union {
                    type types:ipv4-address;
                    type types:ipv4-prefix;
                }
                opd:help "Show kernel route table for a given prefix";
                opd:on-enter "ip -s route list $5";
            }
        }
    }

    opd:augment /op-show:show/op-show-ip-ipv6:ipv6/op-show-ip-ipv6-route:route {
        opd:command forward {
            opd:help "Show kernel IPv6 route table";
            opd:on-enter "show_route_forward --version=ipv6";
            opd:argument prefix {
                type union {
                    type types:ipv6-address;
                    type types:ipv6-prefix;
                }
                opd:help "Show kernel IPv6 route table for a given prefix";
                opd:on-enter "show_route_forward --version=ipv6 --route=$5";
            }
        }
    }
}
