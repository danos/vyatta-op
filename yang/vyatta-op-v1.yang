module vyatta-op-v1 {
	namespace "urn:vyatta.com:mgmt:vyatta-op:1";
	prefix vyatta-op-v1;

	import vyatta-types-v1 {
		prefix types;
	}
	import configd-v1 {
		prefix configd;
	}

	organization "AT&T Inc.";
	contact
		"AT&T
		 Postal: 208 S. Akard Street
		         Dallas, TX 75202
		 Web: www.att.com";

	description
		"Copyright (c) 2017-2019, AT&T Intellectual Property.
		 All rights reserved.
		 Copyright (c) 2014-2016 by Brocade Communications Systems, Inc.
		 All rights reserved.

		 Redistribution and use in source and binary forms, with or without
		 modification, are permitted provided that the following conditions
		 are met:

		 1. Redistributions of source code must retain the above copyright
		    notice, this list of conditions and the following disclaimer.
		 2. Redistributions in binary form must reproduce the above
		    copyright notice, this list of conditions and the following
		    disclaimer in the documentation and/or other materials provided
		    with the distribution.
		 3. Neither the name of the copyright holder nor the names of its
		    contributors may be used to endorse or promote products derived
		    from this software without specific prior written permission.

		 THIS SOFTWARE IS PROVIDED BY THE COPYRIGHT HOLDERS AND CONTRIBUTORS
		 'AS IS' AND ANY EXPRESS OR IMPLIED WARRANTIES, INCLUDING, BUT NOT
		 LIMITED TO, THE IMPLIED WARRANTIES OF MERCHANTABILITY AND FITNESS
		 FOR A PARTICULAR PURPOSE ARE DISCLAIMED. IN NO EVENT SHALL THE
		 COPYRIGHT HOLDER OR CONTRIBUTORS BE LIABLE FOR ANY DIRECT, INDIRECT,
		 INCIDENTAL, SPECIAL, EXEMPLARY, OR CONSEQUENTIAL DAMAGES (INCLUDING,
		 BUT NOT LIMITED TO, PROCUREMENT OF SUBSTITUTE GOODS OR SERVICES;
		 LOSS OF USE, DATA, OR PROFITS; OR BUSINESS INTERRUPTION) HOWEVER
		 CAUSED AND ON ANY THEORY OF LIABILITY, WHETHER IN CONTRACT, STRICT
		 LIABILITY, OR TORT (INCLUDING NEGLIGENCE OR OTHERWISE) ARISING IN
		 ANY WAY OUT OF THE USE OF THIS SOFTWARE, EVEN IF ADVISED OF THE
		 POSSIBILITY OF SUCH DAMAGE.

		 SPDX-License-Identifier: BSD-3-Clause

         Supported RPC calls.
		 Do not add anything to this file.";

	revision 2018-06-14 {
		description "Relocate typedef to prevent compilation failure on
                     older NCS installations.";
	}
	revision 2017-11-06 {
		description "Clarify how values are rounded for ping delay times.";
	}

	revision 2015-08-14 {
		description "Initial revision of version 1.";
	}

	typedef destination {
		type union {
			type types:ip-address;
			type types:ip-prefix;
		}
	}

	rpc ping {
		description "Generates Ping and return response";
		input {
			leaf host {
				type union {
					type types:ip-address;
					type types:domain-name;
				}
				mandatory true;
			}
			leaf count {
				type uint32 {
					range 1..30;
				}
				default 3;
				description "Number of ping echo request message to send";
			}
			leaf ttl {
				type uint8;
				default "255";
				description "IP Time To Live";
			}
		}
		output {
			leaf tx-packet-count {
				type uint32;
				description "Transmitted Packet count";
			}
			leaf rx-packet-count {
				type uint32;
				description "Received packet count";
			}
			leaf min-delay {
				type uint32;
				units "milliseconds";
				description "Minimum packet delay. Any delay less than
				             1ms will show as 0ms.";
			}
			leaf average-delay {
				type uint32;
				units "milliseconds";
				description "Average packet delay. Any delay less than
				             1ms will show as 0ms";
			}
			leaf max-delay {
				type uint32;
				units "millisecond";
				description "Minimum packet delay. Any delay less than
				             1ms will show as 0ms";
			}
		}
		configd:call-rpc "/opt/vyatta/bin/yangop-ping.pl";
	}
	rpc interface {
		input {
			leaf name {
				type string {
					length 1..16;
				}
				mandatory true;
				description "Interface name to query";
			}
		}
		output {
			list address {
				key ip;
				leaf ip {
					type types:ip-prefix;
					description "Interface IP address";
				}
			}
			leaf admin-status {
				type enumeration {
					enum up;
					enum down;
					enum testing;
				}
				description "Interface's desired state";
			}
			leaf oper-status {
				type enumeration {
					enum up;
					enum down;
					enum testing;
					enum unknown;
					enum dormant;
					enum notpresent;
					enum lowerlayerdown;
				}
				description "Interface's current operational state";
			}
			leaf description {
				type string;
				description "Interface description";
			}
		}
		configd:call-rpc "/opt/vyatta/bin/yangop-interface.pl";
	}
	rpc route {
		input {
			leaf family {
				type enumeration {
					enum ipv4;
					enum ipv6;
				}
				default ipv4;
			}
			leaf destination {
				type destination;
				description "Destination host or network";
			}
		}
		output {
			list route {
				key destination;
				leaf destination {
					type destination;
					description "Destination";
				}
				leaf source {
					type types:ip-address;
					description "Source address";
				}
				list path {
					key entry;
					leaf entry {
						type uint64;
					}
					leaf device {
						type string;
						description "Device name";
					}
					leaf next-hop {
						type types:ip-address;
						description "Next-hop";
					}
				}
			}
		}
		configd:call-rpc "/opt/vyatta/bin/yangop-route.pl";
	}
}
